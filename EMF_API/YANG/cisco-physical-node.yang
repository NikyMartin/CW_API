// Copyright (c) 2015 by Cisco Systems, Inc. All rights
// reserved.
//
// Attention: Generated code! Do not modify by hand!
// Generated using Tigerstripe Workbench.
// Generated by: templates/classes/implementation.vm in xmp-yang(5.0.13.qualifier)
// Generated from model: epnm-restconf-xmp-im-ext 
//

module cisco-physical-node {

   namespace "urn:cisco:params:xml:ns:yang:resource:device";
   prefix "nd";

   import ietf-yang-types {
	  prefix yang;
   }
   
   import cisco-physical-foundation-types {
      prefix ctypes;
   }

   import cisco-physical-foundation-ext {
      prefix cext;
   }

//   import cisco-physical-foundation {
//      prefix fdtn;
//   }

   import cisco-physical-foundation-mgr {
      prefix res-mgr;
   }
   
   organization
      "Cisco Systems
      170 West Tasman Drive
      San Jose, CA 95134-1706
      USA";
   contact
      "epnm-yang@cisco.com";
   description
     "EPNM Restconf Mapping Module";
   revision "2016-03-01";  


   // Entities

   container group {
	  uses Group;
      description
         "This object represent automatic and user defined groups to
          which nodes may belong.";
   }
   
   grouping Group {
      reference
         "com.cisco.nms.nbi.epnm.restconf.xmp.im.ext.group";
      description
         "This object represent automatic and user defined groups to
          which nodes may belong.";
      leaf description {
         description
            "Description of the group";
         type string;
         mandatory true;
      }
      leaf name {
         description
            "Name of the group";
         type string;
         mandatory true;
      }
      leaf fdn {
         description
            "The fully qualified domain name (FDN) for the object";
         type string;
         mandatory true;
      }
      container location {
    	 description
    		"The geographic location of the Group";
      }
      
      // Non-containment Associations
      leaf-list contained-group {
         cext:non-containment-association;
         description
            "The child group";
		 type ctypes:nonContainmentAssociatedEntityPath;          
      }

      leaf containing-group {
         cext:non-containment-association;
         description
            "The parent group";
		 type ctypes:nonContainmentAssociatedEntityPath;          
         
      }
      leaf-list node {
         cext:non-containment-association;
         description
            "Nodes within the Group";
		 type ctypes:nonContainmentAssociatedEntityPath;          
      }
   }   
   
   container node {
	  uses Node;
   }
   grouping Node {
      reference
         "com.cisco.nms.nbi.epnm.restconf.xmp.im.ext.RC_Node";
      description
         "This object represents a device managed by EPNM. Also known
          as a managed element (ME).";
      leaf cluster-count {
         type int32;
         mandatory true;
      }
      leaf collection-status {
         description
            "A detailed status of inventory collection - Success or
                failure";
         type string;
         mandatory true;
      }
      leaf collection-time {
         type yang:date-and-time;
         mandatory true;
      }
      leaf communication-state {
         description
            "Indicates management availability or reachability of
                the managed network element. It can indicate the
                availability or reachability of the management agent
                serving as a proxy for the network element.";
         type res-mgr:CommunicationStateEnum;
         mandatory true;
      }
      leaf creation-time {
         type yang:date-and-time;
      }
      leaf description {
         description
            "description of the node";
         type string;
      }
      leaf last-boot-time {
         description
            "Represents the time the management agent on the managed
                network element was last rebooted.";
         type yang:date-and-time;
         mandatory true;
      }
      container latitude {
         description
            "The latitude (in degrees decimal) using the WGS-84
                coordinate system.";
//         uses fdtn:DoubleQuantity;
      }
      leaf lifecycle-state {
         description
            "Represents the current management state of the network
                element: managed, unmanaged, under maintenance, and so
                on. This state is modified by events in the network and
                network management system, and also by user request.";
         type res-mgr:LifecycleStateEnum;
         mandatory true;
      }
      container longitude {
         description
            "The longitude (in degrees decimal) using the WGS-84
                coordinate system.";
//         uses fdtn:DoubleQuantity;
      }
      leaf management-address {
         description
            "The ip address of the device. This is the preferred
                management access address for the device. This is
                typically an address at which SNMP, telnet, and ssh
                agents are available.";
         type string;
         mandatory true;
      }
      leaf name {
         description
            "The name of the MNE.";
         type string;
         mandatory true;
      }
      leaf product-family {
         description
            "The contents of the NAME attribute of the outer-most
                <DEVICEGROUP> element in a Cisco MDF file for this
                particular instance of ManagedNetworkElement.";
         type string;
      }
      leaf product-series {
         description
            "The contents of the NAME attribute of the second-level
                <DEVICEGROUP> element in a Cisco MDF file for this
                particular instance of ManagedNetworkElement.";
         type string;
      }
      leaf product-type {
         description
            "The contents of the NAME attribute of the <DEVICE>
                element in a Cisco MDF file for this particular
                instance of ManagedNetworkElement.";
         type string;
      }
      leaf product-vendor {
         description
            "product vendor";
         type string;
      }
      leaf fdn {
         description
            "The fully qualified domain name (FDN) for the node instance";
         type string;
         mandatory true;
      }
      leaf satellite-count {
         type int32;
      }
      leaf software-family {
         description
            "software Family";
         type string;
      }
      leaf software-type {
         description
            "A string that identifies the specific type of software
                that is installed on this ManagedNetworkElement. For
                example, Cisco IOS or Linux.";
         type string;
      }
      leaf software-version {
         description
            "The specific version of the software (see attribute
                softwareType) that is installed. The value is formatted
                as a text field.";
         type string;
      }
      leaf sys-contact {
         description
            "sysContat of the mne";
         type string;
      }
      leaf sys-location {
         description
            "The physical location of this node (for example,
                'telephone closet, 3rd floor'). If the location is
                unknown, the value is the zero-length string.";
         type string;
      }
      leaf sys-object-id {
         description
            "The vendor's authoritative identification of the
                network management subsystem contained in the element.";
         type string;
      }
      leaf sys-up-time {
         description
            "internal use only";
         type string;
      }
      leaf uuid {
         type string;
         mandatory true;
      }
	  container equipment-list {
		  description
		     "The equipment within the Node";
	  }
      container location {
          description
             "The location of the group";
       }

      // Non-containment Associations
      leaf-list group {
         cext:non-containment-association;
         description
            "Groups containing the Node";
		 type ctypes:nonContainmentAssociatedEntityPath;          
      }
   }  
}
