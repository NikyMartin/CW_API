// Copyright (c) 2009 by Cisco Systems, Inc. All rights
// reserved.
//
// Attention: Generated code! Do not modify by hand!
// Generated using Tigerstripe Workbench.
// Generated by: templates/classes/implementation.vm in (3.1.66)
// Generated from model: cisco-physical-resource-refs
//

module cisco-physical-equipment {
   namespace "urn:cisco:params:xml:ns:yang:restconf:resource:physical";
   prefix eq;

   import ietf-yang-types {
      prefix yang;
   }
   
   import cisco-physical-foundation-types {
      prefix ctypes;
   }

   import cisco-physical-foundation-ext {
      prefix cext;
   }
   
   import cisco-physical-node {
	  prefix nd;
   }

   organization
      "Cisco Systems
      170 West Tasman Drive
      San Jose, CA 95134-1706
      USA";
   contact
      "epnm-yang@cisco.com";
   description
     "The physical resource model.";
   revision "2019-07-26";

   cext:restconf-yang-model;
   // Enumerations

   typedef EquipmentServiceStateEnum {
      description
         "Defines service states for a piece of Equipment (such as in
          service or out of service).";
      reference
         "com.cisco.xmp.model.managed.standardTechnologies.equipment.datatypesAndEnums.EquipmentServiceStateEnum";
      type enumeration {
         enum StandBy {
            value 0;
         }
         enum Unknown {
            value 1;
         }
         enum InService {
            value 2;
         }
         enum OutOfService {
            value 3;
         }
         enum OutOfService_ForMaintenance {
            value 4;
         }
         enum Not_Applicable {
            value 5;
         }
         enum SOFTWARE_DOWNLOAD {
            value 6;
            description
               "Software download in progress";
         }
         enum NOT_INSTALLED {
            value 7;
            description
               "Unequipped";
         }
         enum MISMATCH_OF_EQUIPMENT_ALARM {
            value 8;
            description
               "The plugged cards is not matching the expected card, an alarm
          is raised";
         }
      }
   }

   typedef EquipmentTypeEnum {
      description
         "Defines general types of Equipment that can be used for
          classification.\\nAdding additional values not in the Entity
          MIB starting with index 100 to avoid future clashes";
      reference
         "com.cisco.xmp.model.managed.standardTechnologies.equipment.datatypesAndEnums.EquipmentTypeEnum";
      type enumeration {
         enum Other {
            value 1;
         }
         enum Unknown {
            value 2;
         }
         enum Chassis {
            value 3;
         }
         enum Backplane {
            value 4;
         }
         enum PowerSupply {
            value 6;
         }
         enum Fan {
            value 7;
         }
         enum Module {
            value 9;
            description
               "e.g., plug-in card or daughter-card";
         }
         enum Rack {
            value 18;
         }
         enum PROCESSOR {
            value 100;
            description
               "CPU";
         }
         enum DISK {
            value 101;
            description
               "eg Hard Disk Drive (HDD)";
         }
         enum MEMORY_MODULE {
            value 102;
            description
               "Such as SIMM, DIMM";
         }
         enum COMPUTE_BLADE {
            value 103;
         }
         enum CHASSIS_EXTENDER {
            value 104;
         }
         enum MOTHERBOARD {
            value 105;
         }
         enum IP_PHONE {
            value 106;
         }
         enum WIRELESS_AP {
            value 107;
            description
               "Wireless Access Point";
         }
         enum PLUGGABLE_TRANSCEIVER {
            value 108;
            description
               "SFP, GBIC etc.";
         }
      }
   }

   typedef ModuleResetReasonTypeEnum {
      description
         "Identifies the reason for the last reset performed on the
          module.\\nReference: CISCO-ENTITY-FRU-CONTROL-MIB :
          cefcModuleResetReason";
      reference
         "com.cisco.xmp.model.managed.standardTechnologies.equipment.datatypesAndEnums.ModuleResetReasonTypeEnum";
      type enumeration {
         enum unknown {
            value 1;
         }
         enum powerUp {
            value 2;
         }
         enum parityError {
            value 3;
         }
         enum clearConfigReset {
            value 4;
         }
         enum manualReset {
            value 5;
         }
         enum watchDogTimeoutReset {
            value 6;
         }
         enum resourceOverflowReset {
            value 7;
         }
         enum missingTaskReset {
            value 8;
         }
         enum lowVoltageReset {
            value 9;
         }
         enum controllerReset {
            value 10;
         }
         enum systemReset {
            value 11;
         }
         enum switchoverReset {
            value 12;
         }
         enum upgradeReset {
            value 13;
         }
         enum downgradeReset {
            value 14;
         }
         enum cacheErrorReset {
            value 15;
         }
         enum deviceDriverReset {
            value 16;
         }
         enum softwareExceptionReset {
            value 17;
         }
         enum restoreConfigReset {
            value 18;
         }
         enum abortRevReset {
            value 19;
         }
         enum burnBootReset {
            value 20;
         }
         enum standbyCdHealthierReset {
            value 21;
         }
         enum nonNativeConfigClearReset {
            value 22;
         }
         enum memoryProtectionErrorReset {
            value 23;
         }
      }
   }

   typedef EquipmentRemovalEnum {
      description
         "Defines possible removal states and conditions for a piece of
          Equipment (for example, removable when powered).";
      reference
         "com.cisco.xmp.model.managed.standardTechnologies.equipment.datatypesAndEnums.EquipmentRemovalEnum";
      type enumeration {
         enum Unknown {
            value 0;
         }
         enum Not_Removable {
            value 1;
         }
         enum Removable_Only_Without_Power {
            value 2;
         }
         enum Removable_WithOrWithout_Power {
            value 3;
         }
      }
   }

   // Data types

   // Entities
   grouping Module {
      reference
         "com.cisco.xmp.model.managed.standardTechnologies.equipment.Module";
      description
         "Represents a physical module or adapter card.";
      uses Equipment;
   }
   
   grouping Chassis {
      reference
         "com.cisco.xmp.model.managed.standardTechnologies.equipment.Chassis";
      description
         "A specialization of Equipment that can contain other pieces
          of Equipment (such as enclosure, frame, and so on).";
      uses Equipment;
      leaf is-rack-mountable {
         description
            "Indicates whether the Chassis can be mounted in a Rack.";
         type boolean;
      }
      leaf number-of-free-slots {
         description
            "Indicates the number of free slots the chassis has.";
         type int32;
      }
      leaf number-of-slots {
         description
            "The number of slots in the chassis available for plugin
                modules.";
         type int32;
      }
   }

   grouping PhysicalConnector {
      reference
         "com.cisco.xmp.model.managed.standardTechnologies.equipment.PhysicalConnector";
      description
         "Represents a connector, able to transmit signals or power
          when in a connection. For example, an RJ11 jack (socket) is a
          kind of PhysicalConnector.";

      leaf fdn {
         description
            "Fully-qualified domain name for the object - used by
                Restconf API";
         type string;
      }
      leaf connector-type {
          description
             "The type of connector.\\n\\nsee IANA-MAU-MIB Jack
                 Type\\nother(1) - undefined or unknown\\nrj45(2) -
                 RJ45\\nrj45S(3) - RJ45 shielded\\ndb9(4) - DB9\\nbnc(5)
                 - BNC\\nfAUI(6) - AUI female\\nmAUI(7) - AUI
                 male\\nfiberSC(8) - SC fiber\\nfiberMIC(9) - MIC
                 fiber\\nfiberST(10) - ST fiber\\ntelco(11) -
                 Telco\\nmtrj(12) - MT-RJ fiber\\nhssdc(13) - fiber
                 channel style-2\\nfiberLC(14) - LC fiber\\ncx4(15) -
                 IB4X for 10GBASE-CX4\\nsfpPlusDA(16) - SFP+ Direct
                 Attach for 10GE";
          type string;
       }
       leaf equipment {
          cext:non-containment-association;
          description
             "The instance of Equipment that contains this PhysicalConnector";
          type ctypes:nonContainmentAssociatedEntityPath;
       }
   }
   grouping Equipment {
      reference
         "com.cisco.xmp.model.managed.standardTechnologies.equipment.Equipment";
      description
         "Represents a piece of hardware that has some well-specified
          function (for example, a line card, memory board, or power
          supply). The structure of an Equipment instance can be
          compound so that an instance of Equipment can contain one or
          more instances of Equipment (containment is represented by
          linking two instances of Equipment using the
          EquipmentHasEquipment association).";

      leaf clei-code {
         description
            "This object represents the CLEI (Common Language
                Equipment Identifier) code for the physical entity. If
                the physical entity is not present in the system, or
                does not have an associated CLEI code, the value of
                this object will be
                null.\\n\\nFrom-CISCO-ENTITY-ASSET-MIB : ceAsset.cleI";
         type string;
      }

      leaf ent-physical-index {
         description
            "## Internal use only ##";
         type string;
      }
      leaf equipment-type {
         description
            "An indication of the general hardware type of the
                physical entity. This should be set to the standard
                enumeration value that most accurately indicates the
                general class of the physical entity or the primary
                class if there is more than one. If no appropriate
                standard registration identifier exists for this
                physical entity, the value 'other' is returned.";
//         type eq:EquipmentTypeEnum;
         type string;
      }
      leaf free-slot-names {
         description
            "A comma-separated list of free slot names in the Chassis 
                of supported devices types (currently the NCS-1000 and
                NCS-2000 series). The client can use this list to 
                determine slot availability for network planning 
                applications. For example:
                'SLOT-4-2, SLOT-4-3, SLOT-4-4, SLOT-4-5, SLOT-4-6, SLOT-4-7'
                reports that on SHELF-4 slots 2 through 7 are free.";
         type string;
      }
      leaf hardware-version {
         description
            "The vendor-specific hardware revision string for the
                physical entity. The preferred value is the hardware
                revision identifier actually printed on the component
                itself (if present). If no specific hardware revision
                string is associated with the physical component, or if
                this information is unknown, this will contain a
                zero-length string.";
         type string;
      }
      leaf is-field-replaceable-unit {
         description
            "Indicates whether this physical entity is considered a
                'field replaceable unit' by the vendor.";
//         type fdtn:MultiStateEnum;
         type string;
      }
      leaf is-physically-present {
         type boolean;
         default true;
      }
      leaf is-reporting-alarms-allowed {
         description
            "Indicates whether alarm reporting for this resource is
                allowed (can be set to Not_applicable).";
//         type fdtn:MultiStateEnum;
         type string;
         default Unknown;
      }
      leaf manufactured-date {
         description
            "Contains the date of manufacturing of the equipment. If
                the manufacturing date is unknown or not supported, the
                value of 0 is assigned.";
         type yang:date-and-time;
      }
      leaf manufacturer {
         description
            "The name of the manufacturer of this physical
                component. The preferred value is the manufacturer name
                string actually printed on the component itself (if
                present). If the manufacturer name string associated
                with the physical component is unknown to the agent,
                this object will contain a zero-length string.";
         type string;
      }

      leaf operational-state-code {
         description
            "** Deprecated. Will be replaced by an enumerated
                attribute (possibly a lookup table) after a proper
                model review **\\nThe operational state (operable or
                inoperable) of the equipment.";
         status deprecated;
         type string;
      }
      leaf part-number {
         description
            "Manufacturer's part number.";
         type string;
      }

      leaf product-family {
         description
            "The name of a group of products derived from a common
                product platform. For example, Catalyst 4000, MDS 900.
                Product family can be uniquely determined via the
                productId in Cisco's products databases that contain
                the product, product series, product families, and
                their relationship.";
         type string;
      }
      container position {
          leaf-list position {
             description
                "The name of the container(s)
                 that the Equipment is in, or null if is not contained
                 (for example, chassis).";
             type string;
          }
      }
      leaf product-id {
         description
            "The vendor-specific model name identifier string
                associated with this physical component. The preferred
                value is the customer-visible part number, which might
                be printed on the component itself. The productId
                generated by the device is often referred to as the
                \\\"base PID\\\".\\n\\nFor some applications, PIDs must
                go through a validation process; the resulting PID is
                referred to as a \\\"validated PID\\\".";
         type string;
      }
      leaf product-name {
         description
            "The official name given to a product. For example,
                Cisco 10720 Router or Cisco 10720, Cisco 12000 Series
                Six-Port DS3 Line Card or 6-Port DS3.";
         type string;
      }
      leaf fdn {
         description
            "Fully-qualified domain name for the object - used by
                Restconf API";
         type string;
      }
      leaf serial-number {
         description
            "The vendor-specific serial number string for the
                physical entity. The preferred value is the serial
                number string actually printed on the component itself
                (if present). If a serial number is unknown or
                nonexistent, the SerialNumber will be left null. Note
                that not every physical component has (or needs) a
                serial number. Physical entities, which are not FRU
                (field replaceable) do not need their own unique serial
                number. This item is used for composing the UDI SID
                (see attribute 'udi').";
         type string;
      }
      leaf service-state {
         description
            "Denotes the service state of a physical entity from the
                point of view of the management application. It
                indicates whether the entity is in service, out of
                service, under maintenance, and so on.";
//         type eq:EquipmentServiceStateEnum;
         type string;
         default Unknown;
      }

      leaf udi {
         description
            "Universal Device Identifier. The UDI is composed by
                concatenating the following values:\\nPID =
                Equipment.partNumber\\nVID =
                Equipment.hardwareVersion\\nSN = Equipment.serialNumber";
         type string;
      }
      leaf vendor-equipment-type {
         description
            "An indication of the vendor-specific hardware type of
                the physical entity. Represents an independently
                extensible type identification value. It can, for
                example, indicate a particular subtree with further MIB
                definitions, or define a particular type of protocol or
                hardware (for example,
                1.3.6.1.4.1.9.12.3.1.9.3.131).\\nSee
                CISCO-ENTITY-VENDORTYPE-OID-MIB.";
         type string;
      }
      leaf contained-equipment-recurse {
    	 description
            "## Internal use only ##";
    	 type string;
    	 status deprecated;
      }

      container connectors {
         list physical-connector {
            key fdn;
            uses PhysicalConnector;
         }
      }

      // Non-containment Associations
      leaf-list contained-equipment {
         cext:non-containment-association;
         description
            "A set of instances of Equipment contained in this
             instance of Equipment.";
		 type ctypes:nonContainmentAssociatedEntityPath;
      }
      leaf containing-equipment {
         cext:non-containment-association;
         description
            "The instance of Equipment that contains this instance
                of Equipment (if NULL, this instance is not contained).";
         type ctypes:nonContainmentAssociatedEntityPath;
      }

   }
   container chassis {
       cext:extends eq:equipment;
       uses Chassis;
   }
   
   container equipment {
      uses Equipment;
   }

   container module {
      cext:extends eq:equipment;
      uses Module;
   }
   container physical-connector {
      uses PhysicalConnector;
   }
   
   augment "/nd:node/nd:equipment-list" {
	  list equipment {
	     description
	        "The equipment within the Node";
		 key fdn;
		 uses Equipment;
	  }
   }
}
